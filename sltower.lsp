(defun c:tow()
(if (= IP nil) (setq IP '(0.0 0.0 0.0)))
(if (= venkii nil) (progn
(command "layer" "m" "mem" "c" "4" "" "")
(command "layer" "m" "des" "c" "1" "" "")
(command "layer" "m" "gus" "c" "3" "" "")
(command "layer" "m" "con" "c" "1" "" "")
(command "layer" "m" "dim" "c" "5" "" "")
(command "layer" "m" "len" "c" "2" "" "")
(command "layer" "m" "int" "c" "7" "" "")
(command "layer" "m" "bolt" "c" "6" "" "")
(command "layer" "m" "bdes" "c" "6" "" "")
(command "layer" "m" "das" "c" "1" "" "lt" "dashed" "" "")
(command "layer" "m" "hid" "c" "1" "" "lt" "hidden" "" "")
(command "layer" "m" "cen" "c" "2" "" "lt" "center" "" "")
(command "layer" "s" "0" "")
(defun c:mem  () (command "change" pause "" "p" "la" "mem" "lt" "bylayer" "c" "bylayer" ""))
(defun c:das  () (command "change" pause "" "p" "la" "das" "lt" "bylayer" "c" "bylayer" ""))
(defun c:cen  () (command "change" pause "" "p" "la" "cen" "lt" "bylayer" "c" "bylayer" ""))
(defun c:des  () (command "change" pause "" "p" "la" "des" "lt" "bylayer" "c" "bylayer" ""))
(defun c:gus  () (command "change" pause "" "p" "la" "gus" "lt" "bylayer" "c" "bylayer" ""))
(defun c:con  () (command "change" pause "" "p" "la" "con" "lt" "bylayer" "c" "bylayer" ""))
(defun c:de   () (command "change" pause "" "p" "la" "dim" "lt" "bylayer" "c" "bylayer" ""))
(defun c:bot  () (command "change" pause "" "p" "la" "bolt" "lt" "bylayer" "c" "bylayer" ""))
(defun c:FAB  () (command "change" pause "" "p" "la" "FAB" "lt" "bylayer" "c" "bylayer" "")) ;yellow continus
(defun c:hid  () (command "change" pause "" "p" "la" "das" "lt" "hidden" "" )) ;hidden
(defun c:bl   () (command "change" pause "" "p" "la" "das" "lt" "dashdot" "" ))
(defun c:bdes () (command "change" pause "" "p" "la" "bdes" "lt" "bylayer" "" )) ;majentha continus

(defun mem() (command "change" pause "" "p" "la" "mem" "lt" "bylayer" "c" "bylayer" ""))
(defun das() (command "change" pause "" "p" "la" "das" "lt" "bylayer" "c" "bylayer" ""))
(defun cen() (command "change" pause "" "p" "la" "cen" "lt" "bylayer" "c" "bylayer" ""))
(defun des() (command "change" pause "" "p" "la" "des" "lt" "bylayer" "c" "bylayer" ""))
(defun gus() (command "change" pause "" "p" "la" "gus" "lt" "bylayer" "c" "bylayer" ""))
(defun con() (command "change" pause "" "p" "la" "con" "lt" "bylayer" "c" "bylayer" ""))
(defun de() (command "change" pause "" "p" "la" "dim" "lt" "bylayer" "c" "bylayer" ""))
(defun bot() (command "change" pause "" "p" "la" "bolt" "lt" "bylayer" "c" "bylayer" ""))
(defun FAB() (command "change" pause "" "p" "la" "FAB" "lt" "bylayer" "c" "bylayer" "")) ;yellow continus
(defun hid() (command "change" pause "" "p" "la" "das" "lt" "hidden" "" )) ;hidden
(defun bl() (command "change" pause "" "p" "la" "das" "lt" "dashdot" "" ))
(defun bdes() (command "change" pause "" "p" "la" "bdes" "lt" "bylayer" "" )) ;majentha continus
(setq sf 15)
(command "dimscale" sf)
(command "style" "arial" "arial" (* 4.0 sf) "" "" "" "")
(command "style" "standard" "simplex" (* 2.0 sf) "0.8" "" "" "" "")
(command "style" "SHX_style" "simplex" (* 2.5 sf) "0.8" "" "" "" "")

(command "ltscale" (* 5.0 sf))
(command "dimasz" 2.5)
(command "dimtsz" 0.5)
(command "dimtxt" 2.5)
(command "dimexe" 1)
(command "dimexo" 1)
(command "dimlwd" 9)
(command "dimlwe" 9)
(command "dimgap" 1)
(command "dimtad" 1)
(command "dimtofl" 1)
(command "dimtih" 0)
(command "dimtoh" 0)
(command "dimlwd" 9) 
(command "dimlwe" 9)
(setq venkii "1")
))




 (defun DTR (a)
(* PI (/ a 180.0))
);defun
(defun c:tab()
(setq ip (getpoint "\n pick the point to generate"))

(setq a (ssget))
   (setq n (sslength a))
      (setq ve2 (+ 1 n))
   (setq index 0 )
      (setvar "osmode" 0)
   (setq p1 ip)
      (repeat n
	  (setq ve2 (- ve2 1))
      (setq b1 (entget (ssname a index)))
      (setq index (1+ index))
	  (setq in index)
      (setq bb (assoc 1 b1 ))
	  (setq cc (cdr bb))
	  (setq k1 (cdr (assoc 13 b1)))
	  (setq k2 (cdr (assoc 14 b1)))
	  (setq dis (distance k1 k2))
	  (setq td (/ dis 2))
	  (setq p2 (polar p1 (DTR 180.0) 3800))
	  (setq p3 (polar p1 (DTR 270.0) dis))

	  (setq tp1 (polar p2 (DTR 270.0) td))
	  (setq tp2 (polar tp1 (DTR 0.0) 600))
	  (command "textsize" "300")
	  (command "line" p1 p2 "")
	  (command "TEXT" tp2 "300" "90" ve2 "")
	  (setq p1 p3)
	  	  )
	  (setq p4 (polar p3 (DTR 180.0) 3800))
	  (setq p5 (polar ip (DTR 180.0) 3800))

	  (setq p6 (polar ip (DTR 180.0) 1000))
	  (setq p7 (polar p6 (DTR 180.0) 1000))
	  (setq p8 (polar p7 (DTR 180.0) 1000))

	  (setq p9 (polar p3 (DTR 180.0) 1000))
	  (setq p10 (polar p9 (DTR 180.0) 1000))
	  (setq p11 (polar p10 (DTR 180.0) 1000))
;text box
	  (setq p12 (polar p3 (DTR 270.0) 4700))
	  (setq p13 (polar p4 (DTR 270.0) 4700))

	  (setq p14 (polar p3 (DTR 180.0) 1000))
	  (setq p15 (polar p12 (DTR 180.0) 1000))

	  (setq p16 (polar p3 (DTR 180.0) 2000))
	  (setq p17 (polar p12 (DTR 180.0) 2000))

	  (setq p18 (polar p3 (DTR 180.0) 3000))
	  (setq p19 (polar p12 (DTR 180.0) 3000))
;text box text

	  (setq p20temp (polar p13 (DTR 90.0) 250))

	  (setq p20 (polar p20temp (DTR 0.0) 600))
	  (setq p21 (polar p20 (DTR 0.0) 850))
	  (setq p22 (polar p21 (DTR 0.0) 1100))
	  (setq p23 (polar p22 (DTR 0.0) 1030))

	   (command "line" p3 p4 "")
	   (command "line" ip p3 "")
	   (command "line" p5 p4 "")
	   (command "line" p6 p9 "")
	   (command "line" p7 p10 "")
	   (command "line" p8 p11 "")
	   (command "line" p3 p12 p13 p4 "")
	   (command "line" p14 p15 "" )
	   (command "line" p16 p17 "" )
	   (command "line" p18 p19 "" )

	   (command "TEXT" p20 "300" "90" "PANEL No.S" "")
	   (command "TEXT" p21 "300" "90" "MAIN LEGS SIZES" "")
	   (command "TEXT" p22 "300" "90" "DIAGONALS SIZES" "")
	   (command "TEXT" p23 "300" "90" "HORIZONTALS SIZES" "")
	      (setvar "osmode" 135)

	  )
	  
	  
(defun c:ttt()
(defun DTR(x) (* (/ pi 180.0) x))
(command "ltscale" 400)
(command "dimasz" 25)
(command "dimtsz" 25)
(command "dimexe" 25)
(command "dimexo" 5)
(command "dimlwd" 9)
(command "dimlwe" 9)
(command "dimgap" 1)
(command "dimtad" 1)
(command "dimtofl" 1)
(command "dimtih" 0)
(command "dimtoh" 0)
(if (and (> tower_hight 5000) (<= tower_hight 20000)) (progn (command "style" "standard" "simplex" 180 "0.8" "" "" "" "") (setq vv 180) (command "dimtxt" 180) (setq tab1 (polar basepoint (DTR 180.0) (+ (/ bww 2) 3000)))  (setq tab2 (polar tab1 (DTR 180.0) 1000)) (setq tab3 (polar tab2 (DTR 180.0) 1000)) (setq tab4 (polar tab3 (DTR 180.0) 1000)) (setq tab5 (polar tab4 (DTR 180.0) 800)) ))
(if (and (> tower_hight 20000) (<= tower_hight 40000)) (progn (command "style" "standard" "simplex" 250 "0.8" "" "" "" "") (setq vv 250) (command "dimtxt" 250) (setq tab1 (polar basepoint (DTR 180.0) (+ (/ bww 2) 3000)))  (setq tab2 (polar tab1 (DTR 180.0) 1050)) (setq tab3 (polar tab2 (DTR 180.0) 1050)) (setq tab4 (polar tab3 (DTR 180.0) 1050)) (setq tab5 (polar tab4 (DTR 180.0) 950)) ))
(if (and (> tower_hight 40000) (<= tower_hight 60000)) (progn (command "style" "standard" "simplex" 300 "0.8" "" "" "" "") (setq vv 300) (command "dimtxt" 300) (setq tab1 (polar basepoint (DTR 180.0) (+ (/ bww 2) 3000)))  (setq tab2 (polar tab1 (DTR 180.0) 1100)) (setq tab3 (polar tab2 (DTR 180.0) 1100)) (setq tab4 (polar tab3 (DTR 180.0) 1100)) (setq tab5 (polar tab4 (DTR 180.0) 1000)) ))
(if (and (> tower_hight 60000) (<= tower_hight 80000)) (progn (command "style" "standard" "simplex" 350 "0.8" "" "" "" "") (setq vv 350) (command "dimtxt" 350) (setq tab1 (polar basepoint (DTR 180.0) (+ (/ bww 2) 3000)))  (setq tab2 (polar tab1 (DTR 180.0) 1150)) (setq tab3 (polar tab2 (DTR 180.0) 1150)) (setq tab4 (polar tab3 (DTR 180.0) 1150)) (setq tab5 (polar tab4 (DTR 180.0) 1050)) ))
(if (and (> tower_hight 80000) (<= tower_hight 90000)) (progn (command "style" "standard" "simplex" 400 "0.8" "" "" "" "") (setq vv 400) (command "dimtxt" 400) (setq tab1 (polar basepoint (DTR 180.0) (+ (/ bww 2) 3000)))  (setq tab2 (polar tab1 (DTR 180.0) 1250)) (setq tab3 (polar tab2 (DTR 180.0) 1250)) (setq tab4 (polar tab3 (DTR 180.0) 1250)) (setq tab5 (polar tab4 (DTR 180.0) 1150)) ))
(setq tab_end1 (polar tab1 (DTR 270.0) 3500))
(setq tab_end2 (polar tab5 (DTR 270.0) 3500))
(command "line" tab1 (polar tab1 (DTR 270.0) 3500) "")
(command "line" tab2 (polar tab2 (DTR 270.0) 3500) "")
(command "line" tab3 (polar tab3 (DTR 270.0) 3500) "")
(command "line" tab4 (polar tab4 (DTR 270.0) 3500) "")
(command "line" tab5 (polar tab5 (DTR 270.0) 3500) "")
(command "line" tab_end1 tab_end2 "")
(command "line" tab1 tab5 "")

(command "TEXT" (polar tab5 (DTR 280.0) 3230) "90" "PANEL No.S")
(command "TEXT" (polar tab4 (DTR 280.0) 3245) "90" "MAIN LEGS")
(command "TEXT" (polar tab3 (DTR 280.0) 3245) "90" "DIAGONALS")
(command "TEXT" (polar tab2 (DTR 280.0) 3245) "90" "HORIZONTALS")

(setq dime_start (polar basepoint (DTR 180.0) (+ (/ bww 2) 800)))
(setq index 0)
(setq st dime_start)

(repeat npanels
(setq index (1+ index))
(setq dis (eval (read (strcat "pnum" (rtos index 2 0)))))
(setq end (polar st (DTR 90.0) dis))
(setq tab1_end (polar tab1 (DTR 90.0) dis))
(setq tab2_end (polar tab2 (DTR 90.0) dis))
(setq tab3_end (polar tab3 (DTR 90.0) dis))
(setq tab4_end (polar tab4 (DTR 90.0) dis))
(setq tab5_end (polar tab5 (DTR 90.0) dis))
(command "dim1" "ver" st end (polar st (DTR 180.0) 1000) dis) 
(command "line" tab1 tab1_end "") 
(command "line" tab2 tab2_end "") 
(command "line" tab3 tab3_end "") 
(command "line" tab4 tab4_end "")
(command "line" tab5 tab5_end "")
(command "line" tab1_end tab5_end "")
(setq pnum (polar tab5_end (DTR 0.0) (* (distance tab5 tab4) 0.7)))
(command "TEXT" (polar pnum (DTR 270.0) (/ dis 2)) "90" index)

(setq t_1 (eval (read (strcat "t" (rtos index 2 0)))))
(setq t_2 (eval (read (strcat "t" (rtos index 2 0) "_1" ))))
(setq t_3 (eval (read (strcat "tt" (rtos index 2 0)))))
(setq t_4 (eval (read (strcat "tt" (rtos index 2 0) "_1" ))))
(setq t_5 (eval (read (strcat "ttt" (rtos index 2 0)))))
(setq t_6 (eval (read (strcat "ttt" (rtos index 2 0) "_1" ))))

(if (= vv 180) (progn (setq cl1 (/ (- dis 1825) 2)) (setq cl2 (/ (- dis 1370) 2)) (setq cl3 (/ (- dis 866) 2))))
(if (= vv 250) (progn (setq cl1 (/ (- dis 2032) 2)) (setq cl2 (/ (- dis 1521) 2)) (setq cl3 (/ (- dis 953) 2))))
(if (= vv 300) (progn (setq cl1 (/ (- dis 2435) 2)) (setq cl2 (/ (- dis 1829) 2)) (setq cl3 (/ (- dis 1151) 2))))
(if (= vv 400) (progn (setq cl1 (/ (- dis 3246) 2)) (setq cl2 (/ (- dis 2439) 2)) (setq cl3 (/ (- dis 1529) 2))))

(setq tmp1 (polar tab4 (DTR 0.0) (* (/ (distance tab3 tab4) 2) 0.75)))
(setq tmp2 (polar tab4 (DTR 0.0) (* (distance tab3 tab4) 0.8)))

(command "TEXT" (polar tmp1 (DTR 90.0) cl1) "90" t_1)
(command "TEXT" (polar tmp2 (DTR 90.0) cl2) "90" t_2)

(setq tmp3 (polar tab3 (DTR 0.0) (* (/ (distance tab3 tab2) 2) 0.75)))
(setq tmp4 (polar tab3 (DTR 0.0) (* (distance tab3 tab2)  0.8)))
(command "TEXT" (polar tmp3 (DTR 90.0) cl1) "90" t_3)
(command "TEXT" (polar tmp4 (DTR 90.0) cl3) "90" t_4)

(setq tmp5 (polar tab2 (DTR 0.0) (* (/ (distance tab2 tab1) 2) 0.75)))
(setq tmp6 (polar tab2 (DTR 0.0) (* (distance tab2 tab1) 0.8)))
(command "TEXT" (polar tmp5 (DTR 90.0) cl1) "90" t_5)
(command "TEXT" (polar tmp6 (DTR 90.0) cl3) "90" t_6)

(setq st end)
(setq tab1 tab1_end)
(setq tab2 tab2_end)
(setq tab3 tab3_end)
(setq tab4 tab4_end)
(setq tab5 tab5_end)
)
(command "dim1" "ver" dime_start st (polar st (DTR 180.0) 1500) (strcat (rtos(/ tower_hight 1000) 2 0) " Tower"))

)
